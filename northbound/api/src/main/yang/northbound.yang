module northbound {
    yang-version 1;
    namespace "urn:opendaylight:ansible:northbound";
    prefix "northbound";

    description "Ansible northbound api";

    revision "2018-08-21" {
        description "Initial revision.";
    }

    container commands {
        list command {
            description "Ansible command";
            key "name";
            leaf name {
                type string;
                description "Name of ansible command";
            }
            leaf host {
                type string;
                description "IP/hostname to execute command on";
            }
            leaf directory {
                type string;
                description "path to execute";
            }
            leaf file {
                type string;
                description "role/playbook to execute";
            }
            leaf status {
                type string;
            }
        }
    }
}
